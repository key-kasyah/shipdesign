(defun c:LinesPlan ()
  (command "-layer" "m" "FRAME" "c" "1" "" "")
  (command "-layer" "m" "WATERLINE" "c" "5" "" "")
  (command "-layer" "m" "CENTERLINE" "c" "1" "l" "CENTER" "" "")
  (command "-layer" "s" "FRAME" "")
  (command "SPLINE"
    "-0.0,0"
    "-0.0,1.1"
    "-0.0,2.2"
    "-0.0,3.3"
    "-0.0,4.4"
    "-0.0,5.5"
    "-4.179200000000001,8.112"
    "" "" "")
  (command "-layer" "s" "FRAME" "")
  (command "SPLINE"
    "-0.023764765073218,0"
    "-0.2501808806579144,1.1"
    "-0.6004865443218651,2.2"
    "-1.024898344699135,3.3"
    "-1.5067602538854301,4.4"
    "-2.036411018732097,5.5"
    "-5.559790218732095,8.09072"
    "" "" "")
  (command "-layer" "s" "FRAME" "")
  (command "SPLINE"
    "-0.17512386085218298,0"
    "-0.43829497167064013,1.1"
    "-0.9420846449251776,2.2"
    "-1.6731189588134985,3.3"
    "-2.6145797394988755,4.4"
    "-3.75160619917294,5.5"
    "-6.631887799172941,8.07168"
    "" "" "")
  (command "-layer" "s" "FRAME" "")
  (command "SPLINE"
    "-0.5414648943133623,0"
    "-0.8496306304601089,1.1"
    "-1.3571233405366958,2.2"
    "-2.2212569917813063,3.3"
    "-3.482430032371387,4.4"
    "-5.155368432771751,5.5"
    "-7.403662832771751,8.05488"
    "" "" "")
  (command "-layer" "s" "FRAME" "")
  (command "SPLINE"
    "-1.1686541467344647,0"
    "-1.6049604697131417,1.1"
    "-2.039741744383067,2.2"
    "-2.873717717876386,3.3"
    "-4.251826800637362,4.4"
    "-6.258898873407753,5.5"
    "-7.884703673407752,8.04032"
    "" "" "")
  (command "-layer" "s" "FRAME" "")
  (command "SPLINE"
    "-2.0642317538217574,0"
    "-2.7287504062629946,1.1"
    "-3.0732505336889786,2.2"
    "-3.7565282088036622,3.3"
    "-5.033786673894842,4.4"
    "-7.075389595896561,5.5"
    "-8.0,8.028"
    "" "" "")
  (command "-layer" "s" "FRAME" "")
  (command "SPLINE"
    "-3.201743875880192,0"
    "-4.184866801520317,1.1"
    "-4.456555165949123,2.2"
    "-4.920701082271608,3.3"
    "-5.901346652601525,4.4"
    "-7.6210708583724,5.5"
    "-8.0,8.01792"
    "" "" "")
  (command "-layer" "s" "FRAME" "")
  (command "SPLINE"
    "-4.527452746590918,0"
    "-5.897851436113362,1.1"
    "-6.128843089045521,2.2"
    "-6.353131879701836,3.3"
    "-6.888282202236602,4.4"
    "-7.917530755576694,5.5"
    "-8.0,8.01008"
    "" "" "")
  (command "-layer" "s" "FRAME" "")
  (command "SPLINE"
    "-5.975001905589432,0"
    "-7.776389095424879,1.1"
    "-8.0,2.2"
    "-8.0,3.3"
    "-8.0,4.4"
    "-8.0,5.5"
    "-8.0,8.00448"
    "" "" "")
  (command "-layer" "s" "FRAME" "")
  (command "SPLINE"
    "-5.975001905589432,0"
    "-7.776389095424879,1.1"
    "-8.0,2.2"
    "-8.0,3.3"
    "-8.0,4.4"
    "-8.0,5.5"
    "-8.0,8.00112"
    "" "" "")
  (command "-layer" "s" "FRAME" "")
  (command "SPLINE"
    "5.975001905589432,0"
    "7.776389095424879,1.1"
    "8.0,2.2"
    "8.0,3.3"
    "8.0,4.4"
    "8.0,5.5"
    "8.0,8.0"
    "" "" "")
  (command "-layer" "s" "FRAME" "")
  (command "SPLINE"
    "5.975001905589432,0"
    "7.776389095424879,1.1"
    "8.0,2.2"
    "8.0,3.3"
    "8.0,4.4"
    "8.0,5.5"
    "8.0,8.00224"
    "" "" "")
  (command "-layer" "s" "FRAME" "")
  (command "SPLINE"
    "5.975001905589432,0"
    "7.776389095424879,1.1"
    "8.0,2.2"
    "8.0,3.3"
    "8.0,4.4"
    "8.0,5.5"
    "8.0,8.00896"
    "" "" "")
  (command "-layer" "s" "FRAME" "")
  (command "SPLINE"
    "4.527452746590918,0"
    "5.897851436113362,1.1"
    "6.128843089045521,2.2"
    "6.353131879701836,3.3"
    "6.888282202236602,4.4"
    "7.917530755576694,5.5"
    "8.0,8.02016"
    "" "" "")
  (command "-layer" "s" "FRAME" "")
  (command "SPLINE"
    "3.201743875880192,0"
    "4.184866801520317,1.1"
    "4.456555165949123,2.2"
    "4.920701082271608,3.3"
    "5.901346652601525,4.4"
    "7.6210708583724,5.5"
    "8.0,8.03584"
    "" "" "")
  (command "-layer" "s" "FRAME" "")
  (command "SPLINE"
    "2.0642317538217574,0"
    "2.7287504062629946,1.1"
    "3.0732505336889786,2.2"
    "3.7565282088036622,3.3"
    "5.033786673894842,4.4"
    "7.075389595896561,5.5"
    "8.0,8.056"
    "" "" "")
  (command "-layer" "s" "FRAME" "")
  (command "SPLINE"
    "1.1686541467344647,0"
    "1.6049604697131417,1.1"
    "2.039741744383067,2.2"
    "2.873717717876386,3.3"
    "4.251826800637362,4.4"
    "6.258898873407753,5.5"
    "8.0,8.08064"
    "" "" "")
  (command "-layer" "s" "FRAME" "")
  (command "SPLINE"
    "0.5414648943133623,0"
    "0.8496306304601089,1.1"
    "1.3571233405366958,2.2"
    "2.2212569917813063,3.3"
    "3.482430032371387,4.4"
    "5.155368432771751,5.5"
    "8.0,8.10976"
    "" "" "")
  (command "-layer" "s" "FRAME" "")
  (command "SPLINE"
    "0.17512386085218298,0"
    "0.43829497167064013,1.1"
    "0.9420846449251776,2.2"
    "1.6731189588134985,3.3"
    "2.6145797394988755,4.4"
    "3.75160619917294,5.5"
    "7.9809821991729395,8.14336"
    "" "" "")
  (command "-layer" "s" "FRAME" "")
  (command "SPLINE"
    "0.023764765073218,0"
    "0.2501808806579144,1.1"
    "0.6004865443218651,2.2"
    "1.024898344699135,3.3"
    "1.5067602538854301,4.4"
    "2.036411018732097,5.5"
    "7.3992910187320975,8.18144"
    "" "" "")
  (command "-layer" "s" "FRAME" "")
  (command "SPLINE"
    "0.0,0"
    "0.0,1.1"
    "0.0,2.2"
    "0.0,3.3"
    "0.0,4.4"
    "0.0,5.5"
    "6.5376,8.224"
    "" "" "")
  (princ)
)
